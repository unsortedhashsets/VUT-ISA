XABRAM00-MIB DEFINITIONS ::= BEGIN

IMPORTS
	OBJECT-TYPE, Integer32,	MODULE-IDENTITY FROM SNMPv2-SMI;

org OBJECT IDENTIFIER          ::= { iso 3 }
dod OBJECT IDENTIFIER          ::= { org 6 }
internet OBJECT IDENTIFIER     ::= { dod 1 }
experimental OBJECT IDENTIFIER ::= { internet 3 }

nstAgentPlugins MODULE-IDENTITY
   LAST-UPDATED "202010030000Z"
   ORGANIZATION "BUT FIT - Mikhail Abramov"
   CONTACT-INFO "email: xabram00@stud.fit.vutbr.cz"
   DESCRIPTION  "A simple MIB for ISA purposes."
   ::= { experimental 22 }

nstAgentPluginLogin OBJECT-TYPE
    SYNTAX OCTET STRING (SIZE(8))
    MAX-ACCESS read-only
    STATUS current
    DESCRIPTION
        "Student login"
    ::= { nstAgentPlugins 1 }

nstAgentPluginTimeInRFC3339 OBJECT-TYPE
    SYNTAX OCTET STRING (SIZE(28))
    MAX-ACCESS read-only
    STATUS current
    DESCRIPTION
        "Student login"
    ::= { nstAgentPlugins 2 }

nstAgentPluginInt32 OBJECT-TYPE
    SYNTAX Integer32 (-2147483648..2147483647)
    MAX-ACCESS read-write
    STATUS current
    DESCRIPTION
        "Read-write Int32"
    ::= { nstAgentPlugins 3 }

nstAgentPluginReleaseVersion OBJECT-TYPE
    SYNTAX OCTET STRING (SIZE(0..50))
    MAX-ACCESS read-only
    STATUS current
    DESCRIPTION
        "Student login"
    ::= { nstAgentPlugins 4 }

END
